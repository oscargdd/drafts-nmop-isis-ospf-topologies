module ietf-l3-isis-topology {
  yang-version 1.1;
  namespace
    "urn:ietf:params:xml:ns:yang:ietf-l3-isis-topology";
  prefix "isisnt";
 
  import ietf-network {
    prefix "nw";
    reference
      "RFC 8345: A YANG Data Model for Network Topologies";
  }

  import ietf-network-topology {
    prefix "nt";
    reference
      "RFC 8345: A YANG Data Model for Network Topologies";
  }
 
  import ietf-l3-unicast-topology {
    prefix "l3t";
    reference
      "RFC 8346: A YANG Data Model for Layer 3 Topologies";
  }
 
  import ietf-isis {
    prefix "ietf-isis";
    reference
      "RFC 9130: YANG Data Model for the IS-IS Protocols";
  }


  organization
    "IETF NMOP (Network Management Operations) Working Group";
  contact
    "WG Web:  <https://datatracker.ietf.org/wg/opsawg/>
    WG List:  <mailto:opsawg@ietf.org>
    
    Editor:   Oscar Gonzalez de Dios
              <mailto:oscar.gonzalezdedios@telefonica.com>
    Editor:   Samier Barguil
              <mailto:samier.barguil_giraldo@nokia.com>
    Editor:   Victor Lopez
              <mailto:victor.lopez@nokia.com>
    Editor:   Benoit Claise
              <mailto:benoit.claise@huwaei.com>";
  description
    "This module defines a model for Layer 3 ISIS
     topologies.

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
     
  revision 2022-09-21 {
    description
      "Initial version";
    reference
      "RFC XXXX: A YANG Data Model for Intermediate System to
       Intermediate System (ISIS) Topology"; 
  }

  grouping isis-topology-type {
    description "Identifies the topology type to be ISIS.";
    container isis-topology {
      presence "indicates ISIS topology";
      description
        "The presence of the container node indicates ISIS
        topology";
    }
  }

  grouping isis-link-attributes {
     description "Defines the IS-IS link attributes.";
     container isis-link-attributes {
      description
        "Main Container to identify the ISIS Link Attributes";
     leaf metric {
      type uint32 {
         range "0 .. 16777215";
       }
      description
        "This type defines wide style format of IS-IS metric.";
     }
     leaf level {
      type ietf-isis:level;
      description
        "Level of an IS-IS node - can be level-1,
        level-2 or level-all.";
    }
    } 
  }

  grouping isis-node-attributes {
    description "IS-IS node scope attributes";
    container isis-node-attributes {
        description
          "Main Container to identify the ISIS Node Attributes";
      leaf system-id {
          type ietf-isis:system-id;
          description
            "System-id of the node.";
        }
      leaf level {
          type ietf-isis:level;
          description
            "Level of an IS-IS node - can be level-1,
            level-2 or level-all.";
        }
      leaf-list area-address {
          type ietf-isis:area-address;
          description
            "List of areas supported by the protocol instance.";
        }
      leaf lsp-lifetime {
          type uint16 {
             range "1..65535";
           }
          units "seconds";
          description
            "Lifetime of the router's LSPs in seconds.";
        }
      leaf lsp-refresh-interval {
          type uint16 {
             range "1..65535";
           }
          units "seconds";
          description
            "Refresh interval of the router's LSPs in seconds.";
        }
      }
  }

grouping isis-termination-point-attributes {
    description "IS-IS termination point scope attributes";
    container isis-termination-point-attributes {
       description
      "Indicates the termination point from the
      which the IS-IS is configured. A termination
      point can be a physical port, an interface, etc.";

    leaf interface-type {
      type ietf-isis:interface-type;
      description
        "Type of adjacency (broadcast or point-to-point) to be established 
        for the interface.
        This dictates the type of hello messages that are used.";
    }

    leaf level {
      type ietf-isis:level;
      description
        "Level of an IS-IS node - can be level-1,
        level-2 or level-all.";
    }

    leaf is-passive{
      type boolean;
      description
        "Indicates whether the interface is in passive mode (IS-IS
        not running but network is advertised).";
      }
    }
  }

  augment "/nw:networks/nw:network/nw:network-types" {
    description
      "Introduces new network type for L3 Unicast topology";
    uses isis-topology-type;
  }

  augment "/nw:networks/nw:network/nw:node/l3t:l3-node-attributes" {
    when "/nw:networks/nw:network/nw:network-types/isisnt:isis-topology" {
      description
        "Augmentation parameters apply only for networks with
        isis topology";
    }
    description
      "Augments L3 topology node attributes for IS-IS";
    uses isis-node-attributes;
  }

  augment "/nw:networks/nw:network/nt:link/l3t:l3-link-attributes" {
    when "/nw:networks/nw:network/nw:network-types/isisnt:isis-topology" {
      description
        "Augmentation parameters apply only for networks with
        IS-IS topology";
    }
    description
      "Augments L3 topology link attributes for IS-IS";
    uses isis-link-attributes;
  }



  augment "/nw:networks/nw:network/nw:node/nt:termination-point"+
  "/l3t:l3-termination-point-attributes" {
    when "/nw:networks/nw:network/nw:network-types/isisnt:isis-topology" {
      description
        "Augmentation parameters apply only for networks with
        IS-IS topology";
    }
    description
      "Augments L3 topology termination point attributes for IS-IS";
    uses isis-termination-point-attributes;
  }
}
